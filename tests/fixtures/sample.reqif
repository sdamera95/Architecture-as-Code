# Stage E sample
Synthetic ReqIF for Stage E API smoke test. Hand-authored per OMG ReqIF 1.0 schema.

# Specification: UAV Trade Study

## REQ-001: MassBudget
The UAV total mass shall not exceed 5 kg.

## REQ-002: EnduranceRequirement
The UAV shall sustain flight for at least 30 minutes.

## REQ-003: PowerBudget
Total system power draw shall not exceed battery discharge capacity.
